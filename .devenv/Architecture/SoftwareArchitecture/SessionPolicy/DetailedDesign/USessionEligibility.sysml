package X2CityDetailedUnit_SessionEligibility {
    private import X2CityDetailedSharedContracts::*;
    private import X2CitySharedSoftwareTypes::*;
    private import X2CitySoftwareContract_SessionPolicy::*;
    private import X2CitySoftwareContract_HmiAdapter::HmiRiderSettingsRequest;
    private import X2CitySoftwareContract_AcceleratorInterface::AcceleratorPositionInputPort;
    private import X2CitySoftwareContract_MotorPositionEstimator::MotorPositionInputPort;
    private import X2CitySoftwareContract_TractionControl::*;
    private import X2CityContract_BatteryControl::*;
    private import X2CityContract_SettingsPolicy::*;
    private import X2CitySoftwareContract_BrakeInterface::SoftwareBrakeLeverState;
    // Owner: SC-SESSION; DD-001; UR-SESSION-001; SW-I-004.
    item def SessionEligibilityRecord :> RidingAuthority;
    item def SessionEligibilityObservationRecord :> UnitInformationEnvelope;
    port def SessionEligibilityInputPort {
        doc /* Receives non-accelerator source-specific Ready prerequisites, sensor health and inhibition evidence used to issue or withdraw Session authority. Accelerator composites use acceleratorPositionIn. */
        in item payload:ContextualSoftwareInformation;
    }
    port def RiderSettingsRequestInputPort :> X2CityContract_SettingsPolicy::RiderSettingsRequestInputPort {
        doc /* Receives HMI's concrete qualified level/speed receipt for the current-startup Ready guard. It is not a retained active setting or initialization state. */
        in item payload:HmiRiderSettingsRequest :>> X2CityContract_SettingsPolicy::RiderSettingsRequestInputPort::payload;
    }
    port def SessionEligibilityOutputPort {
        doc /* Publishes the authority record with its generation and expiry for Demand and Traction; it does not prove physical safety. */
        out item payload:SessionEligibilityRecord;
    }
    port def SessionEligibilityObservationOutputPort {
        doc /* Publishes the generic eligibility observation for reporting and legacy consumers without weakening the typed authority route. */
        out item payload:SessionEligibilityObservationRecord;
    }
    port def QualifiedMotionInputPort {
        doc /* Receives U-TRACTION-MOTION's qualified speed, direction and standstill result for existing Session guards; no demand or Hall absence is inferred as standstill. */
        in item payload:QualifiedMotion;
    }
    port def BatteryReadinessAndFaultInputPort { doc /* Receives the typed startup assessment and separate recognized battery/thermal fault evidence for Ready and existing earliest-fault selection. */ in item payload:BatteryReadinessAndFault; }
    port def BatteryStateOfChargeInputPort { doc /* Receives qualified actual SOC for Session's existing low-charge selection; it is not the supplied BMS SOC candidate. */ in item payload:BatteryStateOfCharge; }
    port def BrakeLeverStateInputPort :> X2CitySoftwareContract_SessionPolicy::BrakeLeverStateInputPort { doc /* Receives the exact `BrakeLeverState` composite once, including its software Qualification refinement for source/reason/event-time/context checks. */ in item brakeLeverState:SoftwareBrakeLeverState :>> X2CitySoftwareContract_SessionPolicy::BrakeLeverStateInputPort::brakeLeverState; }
    part def SessionEligibilityEvaluator {
        /* Evaluates current Ready prerequisites and riding-session inhibition to publish authority only when all required facts are current and qualified. Direct sensor-health conditions retain producer source/reason for the existing first-recognized-fault policy, while the independent PlatformHealthRecord retains platform fault/readiness input; this unit owns neither physical proof nor sensor aggregation. */
        port executionTimeIn:ExecutionTimeInputPort;
        port prerequisitesIn:SessionEligibilityInputPort;
        port ridingSettingsIn:RiderSettingsRequestInputPort;
        port acceleratorPositionIn:AcceleratorPositionInputPort;
        port brakeLeverStateIn:BrakeLeverStateInputPort;
        port motorPositionIn:MotorPositionInputPort;
        // A typed current physical-motion result gates Ready; absence is not standstill.
        port motionIn:QualifiedMotionInputPort;
        port batteryReadinessAndFaultIn:BatteryReadinessAndFaultInputPort;
        port stateOfChargeIn:BatteryStateOfChargeInputPort;
        port authorityOut:SessionEligibilityOutputPort;
        port eligibilityObservationOut:SessionEligibilityObservationOutputPort;
    }
}
