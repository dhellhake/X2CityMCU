package X2CitySoftwareContract_SessionPolicy {
    private import X2CitySharedSoftwareTypes::*;
    private import X2CitySoftwareContract_HmiAdapter::HmiRiderSettingsRequest;
    private import X2CityContract_BatteryControl::*;
    private import X2CityContract_SettingsPolicy::*;
    private import X2CitySoftwareContract_BrakeInterface::SoftwareBrakeLeverState;
    port def BrakeLeverStateInputPort :> X2CityContract_BrakeStateIdentification::BrakeLeverStateInputPort {
        doc /* Receives the exact current `BrakeLeverState` composite. Session evaluates its State and Qualification together using caller-supplied ExecutionTime; it does not receive a separate brake-health route. */
        in item brakeLeverState:SoftwareBrakeLeverState :>> X2CityContract_BrakeStateIdentification::BrakeLeverStateInputPort::brakeLeverState;
    }
    port def RidingReadinessInputPort {
        doc /* Receives heterogeneous non-accelerator current-context facts used to determine Ready eligibility, including rider inputs, settings, health and battery/traction observations. Accelerator composites use the dedicated acceleratorPositionIn port. */
        in item payload:ContextualSoftwareInformation;
    }
    port def RidingSettingsRequestInputPort :> X2CityContract_SettingsPolicy::RiderSettingsRequestInputPort {
        doc /* Receives the current qualified HMI level/speed receipt for the Ready guard. Initialization, retained values and link state are not receipts. */
        in item payload:HmiRiderSettingsRequest :>> X2CityContract_SettingsPolicy::RiderSettingsRequestInputPort::payload;
    }
    port def QualifiedMotionInputPort {
        doc /* Receives explicitly qualified physical motion and standstill evidence from TractionControl for the Ready guard. Electrical Hall edge absence, command absence or retained settings cannot substitute for this record. */
        in item payload:QualifiedMotion;
    }
    attribute def AuthorityGeneration;
    item def SoftwareSelectedFaultIndication :> ContextualSoftwareInformation, X2CityContract_SessionPolicy::SelectedFaultIndication;
    item def RidingAuthority:>ContextualSoftwareInformation, X2CityContract_SessionPolicy::RidingAuthority {
        attribute authorityGeneration:AuthorityGeneration;
        attribute authorityDecisionSequence:Integer;
        attribute authorityDecisionTimeMicroseconds:Integer;
        attribute authorityExpiryTimeMicroseconds:ExpiryTimeMicroseconds :>> X2CityContract_SessionPolicy::RidingAuthority::expiry;
    }
    port def RidingAuthorityOutputPort {
        doc /* Publishes independently generated authority with decision sequence, host-boot monotonic decision time and independent expiry to DemandPolicy and TractionControl. A newer command or observation cannot refresh this authority. */
        out item payload:RidingAuthority;
    }
    port def SelectedFaultIndicationOutputPort :> X2CityContract_SessionPolicy::SelectedFaultIndicationOutputPort {
        doc /* Publishes Session's already-selected qualified fault/no-error indication for HMI encoding. It does not perform physical torque withdrawal or display acknowledgement. */
        out item selectedFaultIndication:SoftwareSelectedFaultIndication :>> X2CityContract_SessionPolicy::SelectedFaultIndicationOutputPort::selectedFaultIndication;
    }
}

package X2CitySoftwareComponent_SessionPolicy {
    private import X2CitySharedSoftwareTypes::*;
    private import X2CitySoftwareContract_AcceleratorInterface::AcceleratorPositionInputPort;
    private import X2CitySoftwareContract_MotorPositionEstimator::MotorPositionInputPort;
    private import X2CitySoftwareContract_SessionPolicy::*;
    private import X2CitySoftwareContract_Platform::*;
    private import X2CityContract_BatteryControl::*;
    part def SessionPolicy {
        /* Forms Ready eligibility, retains current riding-session inhibition, and selects the
           reportable fault/session status. It issues authority generation and expiry for consumers;
           physical torque withdrawal and input self-test execution remain allocated elsewhere. */
        port executionTimeIn:ExecutionTimeInputPort;
        port ridingReadinessIn:RidingReadinessInputPort;
        port ridingSettingsIn:RidingSettingsRequestInputPort;
        port batteryReadinessAndFaultIn:BatteryReadinessAndFaultInputPort;
        port stateOfChargeIn:BatteryStateOfChargeInputPort;
        port acceleratorPositionIn:AcceleratorPositionInputPort;
        port brakeLeverStateIn:BrakeLeverStateInputPort;
        // The complete estimator record delivers fault evidence without adding a Ready guard.
        port motorPositionIn:MotorPositionInputPort;
        port qualifiedMotionIn:QualifiedMotionInputPort;
        port ridingAuthorityOut:RidingAuthorityOutputPort;
        port selectedFaultOut:SelectedFaultIndicationOutputPort;
        // R-V08 is the startup/reset context dependency; R-V31 is the common local family.
        port startupContextIn:~PlatformContextOutputPort;
        port platformContextIn:~PlatformContextOutputPort;
        port platformHealthIn:~PlatformHealthOutputPort;
    }
}
