package X2CityDetailedUnit_BatteryProtectionRestriction {
    private import X2CitySharedSoftwareTypes::*;
    private import X2CityDetailedSharedContracts::*;
    private import X2CityDetailedUnit_BatteryProtectionEvaluate::*;
    private import X2CityContract_BatteryControl::*;
    private import X2CitySoftwareContract_BatteryProtection::*;
    // Owner: SC-BAT-POLICY.V; DD-002. It owns battery electrical restrictions and retains no battery-fault latch.
    port def BatteryAssessmentCandidateInputPort {
        doc /* Receives evaluated charge/discharge candidates before applying battery electrical restrictions and operation context. */
        in item payload:BatteryAssessmentCandidate;
    }
    port def BatteryStatusOutputPort { doc /* Publishes reporting-only independent recognized battery fault, local thermal fault, and qualified MOS-disabled warning conditions, with fault recognition ordering, independent of operating-limits qualification. */ out item payload:BatteryStatus; }
    port def BatteryOperatingLimitsOutputPort { doc /* Publishes the battery electrical operating-limit record to RidingControl Eligibility and Demand. Shared required checks are assessed internally and included in each dependent branch qualification; no common qualification flag is published. Each branch includes its applicable startup, configuration, 14-group and protection/path checks. Each qualified effective current limit equals the exact minimum of its computed pack ceiling and every other applicable qualified battery-side current ceiling or restriction; a qualified disabled/prohibited path contributes zero. Missing or unqualified required applicable constraints leave the dependent branch unqualified with effective zero, not omitted. With no other lower limit, publish the computed pack ceiling. No arbitrary additional derating is permitted. A qualified zero is valid known capability. A qualified disabled charge/discharge path sets only its corresponding current limit to zero and retains that branch qualification when remaining applicable checks pass. OFF status alone does not establish a fault or physical isolation; recognized faults remain reported under existing rules. Unknown shared protection/path state leaves dependent branches unqualified and the separately published MOS status unqualified. An enabled path removes only its path restriction and does not establish positive capability. BatteryProtection retains voltage, temperature and SOC-at-90%-charge-acceptance restrictions on the affected electrical current branches; a no-charge state carries zero regenerative-charge current. It publishes no wheel-torque or speed ceiling. */ out item payload:BatteryOperatingLimitsAssessment; }
    port def BatteryStateOfChargeOutputPort { doc /* Publishes BatteryProtection's qualified actual SOC for HMI presentation and Session low-charge selection. */ out item payload:BatteryStateOfCharge; }
    port def BatteryCurrentOutputPort { doc /* Publishes BatteryProtection's qualified signed pack current for HMI presentation. */ out item payload:BatteryCurrent; }
    part def BatteryCapabilityRestrictor {
        /* Applies operation context to battery envelope candidates and publishes electrical discharge/charge restrictions. Combine bmsStatusIn only into reporting, never into capability assessment or qualification. Preserve candidate qualification and zero effective limits when unqualified while applying ordinary restrictions and exact minimum selection. Never inspect candidate status or bmsStatusIn to decide limits; it owns no fault latch. It does not own vehicle positive-propulsion policy or provide physical protection. */
        port executionTimeIn:ExecutionTimeInputPort; port candidateIn:BatteryAssessmentCandidateInputPort; port bmsStatusIn:BatteryStatusInputPort; port statusOut:BatteryStatusOutputPort; port operatingLimitsOut:BatteryOperatingLimitsOutputPort; port stateOfChargeOut:BatteryStateOfChargeOutputPort; port batteryCurrentOut:BatteryCurrentOutputPort; }
}
