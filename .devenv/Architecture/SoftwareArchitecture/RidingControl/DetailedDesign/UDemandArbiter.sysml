package X2CityDetailedUnit_DemandArbiter {
    private import X2CityDetailedSharedContracts::*;
    private import X2CitySharedSoftwareTypes::*;
    private import X2CitySoftwareContract_AcceleratorInterface::*;
    private import X2CitySoftwareContract_BrakeInterface::SoftwareBrakeLeverState;
    private import X2CitySoftwareContract_RidingControl::*;
    private import X2CityContract_BatteryControl::*;
    private import X2CitySoftwareContract_BatteryProtection::*;
    private import X2CitySoftwareContract_TractionControl::*;
    private import X2CitySoftwareContract_Platform::*;
    // Owner: SC-RIDING-CONTROL; DD-001; UR-DEMAND-001; SW-I-001..005.
    port def DemandAcceleratorInputPort {
        doc /* Receives U-ACCELERATOR-QUALIFY's composite. It uses Position as the active-profile request source only when contained Qualification supports it, and retains the health evidence when Position is unavailable. */
        in item payload:AcceleratorPosition;
    }
    port def DemandBrakeLeverStateInputPort :> X2CitySoftwareContract_RidingControl::BrakeLeverStateInputPort {
        doc /* Receives U-BRAKE-QUALIFY's exact State/Qualification composite; qualified Left, Right or Both blocks only the positive branch. */
        in item brakeLeverState:SoftwareBrakeLeverState :>> X2CitySoftwareContract_RidingControl::BrakeLeverStateInputPort::brakeLeverState;
    }
    port def DemandActiveSettingsInputPort {
        doc /* Receives U-SET-STATE's active level 0–5 and active normalized speed limit; pending settings cannot enter this port. */
        in item payload:X2CitySoftwareContract_RidingControl::ActiveRidingSettings;
    }
    port def DemandAuthorityInputPort {
        doc /* Receives Session authority with independent generation, decision and expiry timestamps; matching generation never prolongs authority expiry. */
        in item payload:X2CitySoftwareContract_RidingControl::RidingAuthority;
    }
    port def DemandBatteryOperatingLimitsInputPort {
        doc /* Receives independently qualified discharge and regenerative-charge current limits and reasons. An unqualified or zero regenerative-charge current limit suppresses the requested regenerative-braking torque under the existing no-charge policy, regardless of instantaneous net pack current. Both amperage limits propagate alongside the wheel request; Traction selects by actual electrical transfer, never wheel-torque sign. */
        in item payload:BatteryOperatingLimitsAssessment;
    }
    port def DemandStateOfChargeInputPort {
        doc /* Receives qualified actual SOC for RidingControl's positive-propulsion 10% cutoff. Positive demand is permitted only above 10%; unqualified SOC cannot establish eligibility. */
        in item payload:BatteryStateOfCharge;
    }
    port def DemandMotionInputPort {
        doc /* Receives qualified vehicle speed, direction and standstill from U-TRACTION-MOTION for cutoffs, recovery and rearm guards. */
        in item payload:QualifiedMotion;
    }
    port def DemandActualOutputInputPort {
        doc /* Receives U-TRACTION-ACTUAL-OUTPUT's qualified applied-wheel-torque estimate and powered-forward evidence for post-stop regen rearm. */
        in item payload:X2CitySharedSoftwareTypes::ActualTractionOutput;
    }
    port def DemandPlatformContextInputPort {
        doc /* Receives the current platform context that invalidates Demand state and prevents an old decision from crossing a reset boundary. */
        in item payload:PlatformContext;
    }
    port def DemandPlatformHealthInputPort {
        doc /* Receives platform health that can withdraw both torque signs without inventing a Session fault latch. */
        in item payload:PlatformHealth;
    }
    port def DemandCommandOutputPort {
        doc /* Sends the signed requested wheel torque, decision sequence and independently expiring command to U-TRACTION-ACCEPT; it is a request, never output evidence. */
        out item payload:WheelTorqueRequest;
    }
    part def DemandArbiter {
        /* Atomically evaluates current qualified rider, active-setting, authority, capability,
           motion and actual-output snapshots. It emits requestedWheelTorqueNewtonMetres with
           independent authority generation and command expiry. Pending settings, a command or PWM/register state never establish
           motion, actual applied torque, powered-forward travel or post-stop regen rearm. */
        port executionTimeIn:ExecutionTimeInputPort;
        port acceleratorIn:DemandAcceleratorInputPort;
        port brakeLeverStateIn:DemandBrakeLeverStateInputPort;
        port activeSettingsIn:DemandActiveSettingsInputPort;
        port authorityIn:DemandAuthorityInputPort;
        port batteryOperatingLimitsIn:DemandBatteryOperatingLimitsInputPort;
        port stateOfChargeIn:DemandStateOfChargeInputPort;
        port motionIn:DemandMotionInputPort;
        port actualOutputIn:DemandActualOutputInputPort;
        port platformContextIn:DemandPlatformContextInputPort;
        port platformHealthIn:DemandPlatformHealthInputPort;
        attribute compiledCalibrationId:String;
        attribute compiledDemandPolicyCalibration:DemandPolicyCalibration;
        attribute compiledCalibrationValid:Boolean;
        attribute lastStateOfChargeReceiptTimeMicroseconds:Integer;
        port commandOut:DemandCommandOutputPort;
    }
}
