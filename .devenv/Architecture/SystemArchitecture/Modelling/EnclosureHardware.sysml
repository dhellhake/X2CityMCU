package X2CityComponent_EnclosureHardware {
    private import X2CitySharedContracts::*;
    part def EnclosureHardware /* Provides the physical enclosure and environmental protection for installed equipment. This supplied hardware role has no project software behavior. */; // LE-ENCLOSURE-HW
}
