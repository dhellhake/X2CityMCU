package X2CityComponent_CarrierHardware {
    private import X2CitySharedContracts::*;
    part def CarrierHardware /* Provides the physical carrier/support structure for the installed vehicle equipment. This supplied hardware role has no project software behavior. */; // LE-CARRIER-HW
}
