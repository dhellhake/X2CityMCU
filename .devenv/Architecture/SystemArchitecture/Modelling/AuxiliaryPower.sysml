package X2CityComponent_AuxiliaryPower {
    private import X2CitySharedContracts::*;
    part def AuxiliaryPower /* Supplies and distributes electrical power for the auxiliary lighting function. This is a physical power boundary; its implementation is outside the logical policy model. */; // LE-AUX-POWER
}
