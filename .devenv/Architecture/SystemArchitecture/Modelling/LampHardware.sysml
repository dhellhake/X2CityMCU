package X2CityComponent_LampHardware {
    private import X2CitySharedContracts::*;
    part def LampHardware /* Provides physical lamps and their light actuation function in response to the auxiliary boundary. This supplied hardware role has no project software behavior. */; // LE-LAMP-HW
}
