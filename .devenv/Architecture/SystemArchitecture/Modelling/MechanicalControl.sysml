package X2CityComponent_MechanicalControl {
    private import X2CitySharedContracts::*;
    part def MechanicalControl /* Represents the physical mechanical control boundary associated with the vehicle. It supplies mechanical handling and actuation context outside the EPCS logical software allocation. */; // LE-MECH; physical mechanical control boundary
}
