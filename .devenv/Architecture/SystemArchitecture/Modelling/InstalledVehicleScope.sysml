package X2CityComponent_InstalledVehicleScope {
    private import X2CitySharedContracts::*;
    // LE-VEH is an installed-vehicle scope view, not a parent of the whole EPCS.
    // The fitted physical pack is singular and is not duplicated by this scope view.
    part def InstalledVehicleScope /* Represents the installed-vehicle scope used to relate the project equipment to the fitted vehicle. */;
}
