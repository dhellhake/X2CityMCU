package X2CityComponent_HarnessHardware {
    private import X2CitySharedContracts::*;
    part def HarnessHardware /* Provides physical wiring, connectors, and routing between installed equipment boundaries. This supplied integration hardware role has no project software behavior. */; // LE-HARNESS-HW
}
