package X2CityComponent_Cells {
    private import X2CitySharedContracts::*;
    part def Cells /* Supplies the battery cell energy-storage function within the physical pack. This supplied energy source is modeled as a hardware role, with no project software implementation implied. */; // LE-CELLS
}
