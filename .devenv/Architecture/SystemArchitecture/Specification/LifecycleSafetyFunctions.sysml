package X2CitySpecification_X2CityMCU_LifecycleSafetyFunctions {
    private import X2CitySystemArchitecture::X2CityMCU;
    private import RequirementTypes::*;

    requirement <'REQ-VEH-FSC-010'> accessibleElectricalContactTemperature : SystemRequirement {
        doc /*
            Original source:
            .devenv/Requirements/System_Requirements/Lifecycle_Safety_Functions.md#req-veh-fsc-010 (line 9).
            Original target: LE-EPCS.
            Original type: System Requirement.
            Status: Draft.
            ID: <a id="req-veh-fsc-010"></a>`REQ-VEH-FSC-010`
            Original obligation column: Obligation
            Derived from safety goal(s): [SG-009](../../../Safety/SG-001_Safety_Goals.md#sg-009)
            Current logical owner / contribution: `LE-EPCS`, with `LE-TRACTION` contributing motor/inverter
            thermal sources and states. Scope covers heat generated by project electrical equipment in
            installed, detached-pack handling and service states.
            Sources (supporting obligations): [REQ-SYS-ENE-001](EnergyAndProtection.sysml),
            [REQ-SYS-ENE-003](EnergyAndProtection.sysml), [REQ-SYS-STO-001](EnvironmentAndStorage.sysml),
            [REQ-SYS-STO-002](EnvironmentAndStorage.sysml)
            Planned measurable verification: `I`, `A`, `T-SYS`, `T-FI`: identify accessible project
            electrical surfaces and relevant operating, storage, service and assigned electrical-fault
            states; qualify temperature against derived contact-duration/material criteria, including
            residual heat after shutdown.
            Open dependencies / qualifications: `OI-041`, `OI-045`, `OI-048`, `OI-056`, `OI-063`: derive
            electrical contact model, exposure duration and fault-energy cases. No passive chassis
            solar-heating criterion, mechanical surface requirement, temperature limit, barrier, cooling
            feature or test standard is invented.
        */
        subject owner:X2CityMCU =
            X2CitySystemArchitecture::x2CityVehicle.epcs;
        require constraint {
            doc /*
                **Draft:** EPCS-supplied electrical/electronic equipment and the removable battery shall
                limit accessible contact temperature caused by electrical operation or fault energy to a
                non-hazardous condition for the applicable material, contact location and exposure duration.
                Passive solar-heated chassis/platform surfaces are outside this project requirement.
            */
        }
    }
    satisfy accessibleElectricalContactTemperature by X2CitySystemArchitecture::x2CityVehicle.epcs;

}
