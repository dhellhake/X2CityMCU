package RequirementTypes {
    requirement def SystemRequirement {
        doc /* System-level requirement classification for a logical system target. */
    }

    requirement def AbstractSoftwareRequirement {
        doc /* Abstract requirement classification for a software responsibility allocated to a logical system target; realization may remain pending. */
    }

    requirement def AbstractHardwareRequirement {
        doc /* Abstract requirement classification for a logical leaf wholly within physical hardware scope. */
    }
}
